Attribute VB_Name = "Excel_Spec"

Sub Creating_Specification()
'--------проверка юзера------------------
Dim msg, Style, Title, Ctxt, Response, MyString
msg = "Вы уверены, что открыли все необходимые файлы для формирования списка и закрыли ненужные?" & (Chr(13)) & "Для продолжения работы нажмите 'YES', если не все файлы открыты/закрыты нажмите 'NO'"   ' Define message.
Style = vbYesNo ' Definde buttons.
Title = "Макрос для формирования сводного списка листов в открытых файлах"    ' Define title.
'Ctxt = 1000    ' Define topic
        ' context.
        ' Display message.
Response = MsgBox(msg, Style, Title)
If Response = vbYes Then    ' User chose Yes.
'--------------начало работы основной части программы------------
Dim list(0 To 100, 1 To 1000) As Variant
'#0 - filename
'#1 - Sheet.name; #2 - Sheet.tabOrder; #3 - Sheet.ObjectID; #4 - Sheet.name_short;
'#5 - Stamp.ObjectID; #6 - Stamp.sheetnum; #7 - Stamp.sheetname1; #8 - Stamp.sheetname2; #9 - Stamp.sheetname3
Dim File As AcadDocument
Dim Sheet As AcadLayout
Dim Sheets(1 To 100) As AcadLayout
Dim Stamp As AcadBlockReference
Dim iStamp As Integer
Dim varAttributes As Variant
Dim strAttributes As String
Dim tagstr As String
Dim j As Integer

i = 1
Dim Layouts As AcadLayouts, Layout As AcadLayout
Dim N, k As Integer
Dim iTab As AcadTable
Dim MyItem As AcadEntity

'--------Экспорт в таблицу Excel-------------------
    Dim Excel As Object
    Dim elem As Object
    Dim excelSheet As Object
    Dim ExcelBook As Object
    
    ' Start Excel
    On Error Resume Next
    
    Set Excel = GetObject(, "Excel.Application")
    
    If Err <> 0 Then
        Err.Clear
        Set Excel = CreateObject("Excel.Application")
            
        If Err <> 0 Then
            MsgBox "Could not load Excel.", vbExclamation
            End
        End If
    End If
    
    On Error GoTo 0
'--------Формирование столбца простых имен (т.е. без формата листа)
'For N = 1 To i
'list(4, N) = Right(list(1, N), Len(list(1, N)) - InStr(1, list(1, N), " "))
'list(10, N) = list(7, N) & " " & list(8, N) & " " & list(9, N)
'Next N


    
    ' Создается лист1 в Excel
    
   Dim NFile
    
    'file = "C:\Program Files\AutoCAD 2006\Support\ШТАМП.xls" 'InputBox("Введите путь и имя сводной таблицы", , "C:\Program Files\AutoCAD 2005\Support\ШТАМП.xls")
    NFile = "C:\Documents and Settings\All Users\Документы\ListOfSpecS.xls" '"C:\ListOfWorkSheets.xls"
    Excel.Visible = True
    'Set ExcelBook = Excel.Workbooks.Open(file)
    Set ExcelBook = Excel.Workbooks.Add
    'ExcelBook.Sheets("ШТАМП").Select
    'Set excelSheet = Excel.ActiveWorkbook.Sheets("ШТАМП")
    Set excelSheet = Excel.ActiveWorkbook.ActiveSheet
    
     '---------------------------------------------------------------------

excelSheet.cells(1, 1).Value = "ФАЙЛ"
excelSheet.cells(1, 2).Value = "ЛИСТ"
excelSheet.cells(1, 3).Value = "№ листа в файле"
excelSheet.cells(1, 4).Value = "Шифр"
excelSheet.cells(1, 5).Value = "Адрес объекта"
excelSheet.cells(1, 6).Value = "Название подсистемы"
excelSheet.cells(1, 7).Value = "Название документа"
excelSheet.cells(1, 8).Value = "Поз."
excelSheet.cells(1, 9).Value = "Обозначение"
excelSheet.cells(1, 10).Value = "Наименование"
excelSheet.cells(1, 11).Value = "Кол."
excelSheet.cells(1, 12).Value = "Масса"
excelSheet.cells(1, 13).Value = "Примечание"
   
 i = 2
'--------------------------------------
'--------------------------------------
For Each File In ThisDrawing.Application.Documents
    Set Layouts = File.Layouts
    For Each Sheet In Layouts
        If Sheet.Name <> "Model" And Sheet.Name <> "Модель" Then
        
'            i = i + 1
            ' обработка блоков
            For k = 0 To Sheet.Block.Count - 1
                If Sheet.Block.Item(k).ObjectName = "AcDbBlockReference" Then
                Set Stamp = Sheet.Block.Item(k)
            ' содержимое основного штампа
                If Stamp.Name = "Stamp3" Or Stamp.Name = "Stamp6" Then ' Or "Stamp" Then '------------проверка какой штамп форма4 или 6
                    excelSheet.cells(i, 1).Value = File.Name
                    excelSheet.cells(i, 2).Value = Sheet.Name
                    excelSheet.cells(i, 3).Value = Sheet.TabOrder
                    varAttributes = Stamp.GetAttributes
                    For j = LBound(varAttributes) To UBound(varAttributes)
                        tagstr = varAttributes(j).TagString
                        Select Case tagstr
                            Case "DOCUMENTID"
                                excelSheet.cells(i, 4).Value = varAttributes(j).TextString
                            Case "OBJECT_ADDRESS"
                                excelSheet.cells(i, 5).Value = varAttributes(j).MTextAttributeContent
                            Case "SUBSYSTEM_NAME"
                                excelSheet.cells(i, 6).Value = varAttributes(j).TextString
                            Case "DOCUMENT_NAME"
                                excelSheet.cells(i, 7).Value = varAttributes(j).MTextAttributeContent
                            End Select
                        Next j
                        
                        'If excelSheet.cells(i, 7).Value = "План расположения оборудования и проводок" Or excelSheet.cells(i, 7).Value = "План расположения" Then
                        'экспорт таблицы со спецификацией элементов
                        'Index = 0
                        
                        'For Index = 0 To File.PaperSpace.Count - 1
                        '    Set MyItem = File.PaperSpace.Item(Index)   '= 1 To Sheet.Block.ObjectName
                        For Index = 0 To Sheet.Block.Count - 1
                            Set MyItem = Sheet.Block.Item(Index)
                            'excelSheet.cells(Index + 1, 1).Value = MyItem.ObjectName
                            If MyItem.ObjectName = "AcDbTable" Then
                                Set iTab = MyItem
                                If iTab.Columns = 6 Then
                                    For row = 1 To iTab.Rows - 1
                                        For col = 0 To iTab.Columns
                                            'iTab.FormatValue (row, col,kFormatOptionNone,
                                            'excelSheet.cells(i + row - 1, col + 8).Value = iTab.GetText(row, col) 'GetTextString(row, col, 0) '
                                            txt = iTab.GetText(row, col)
                                            If InStr(1, txt, "{") = 1 Then
                                                ptxt = InStr(txt, ";")
                                                While ptxt > 0
                                                    txt = Right(txt, Len(txt) - ptxt)
                                                    ptxt = InStr(txt, ";")
                                                    Wend
                                                txt = Left(txt, Len(txt) - 1)
                                                End If
                                            excelSheet.cells(i + row - 1, col + 8).Value = txt
                                            excelSheet.cells(i + row, col + 1).Value = excelSheet.cells(i, col + 1).Value
                                            Next col
                                        Next row
                                        i = i + iTab.Rows
                                End If
                            End If
                            Next Index
                        'End If
                    End If
                    End If
                Next k
            End If
        Next Sheet
       File.Close False
Next File

    'Excel.Cells.Select
    'Excel.Cells.Replace What:="\P", Replacement:="", LookAt:=xlPart, SearchOrder:=xlByRows, MatchCase:=False, SearchFormat:=False, ReplaceFormat:=False
    'Excel.Cells.Replace What:="{\LМонтажные материалы", Replacement:="", LookAt:=xlPart, SearchOrder:=xlByRows, MatchCase:=False, SearchFormat:=False, ReplaceFormat:=False



Excel.ActiveWorkbook.SaveAs NFile, , , , , , , xlLocalSessionChanges
'Excel.Range("A1").Select
'ThisDrawing.Application.Visible = True
    'MsgBox "Все готово... Смотри Excel..."
Else    ' User chose No.
    MsgBox "Сделайте это..."
End If
End Sub


Sub import_Specification_to_cad()
'--------проверка юзера------------------
Dim msg, Style, Title, Ctxt, Response, MyString
msg = "Вы уверены, что открыли все необходимые файлы для формирования списка и закрыли ненужные?" & (Chr(13)) & "Для продолжения работы нажмите 'YES', если не все файлы открыты/закрыты нажмите 'NO'"   ' Define message.
Style = vbYesNo ' Definde buttons.
Title = "Макрос для выгрузки спецификаций обратно на листы"    ' Define title.
'Ctxt = 1000    ' Define topic
        ' context.
        ' Display message.
Response = MsgBox(msg, Style, Title)
If Response = vbYes Then    ' User chose Yes.
'--------------начало работы основной части программы------------
'#0 - filename
'#1 - Sheet.name; #2 - Sheet.tabOrder; #3 - Sheet.ObjectID; #4 - Sheet.name_short;
'#5 - Stamp.ObjectID; #6 - Stamp.sheetnum; #7 - Stamp.sheetname1; #8 - Stamp.sheetname2; #9 - Stamp.sheetname3
Dim File As AcadDocument
Dim Sheet As AcadLayout
Dim Sheets(1 To 100) As AcadLayout
Dim Stamp As AcadBlockReference
Dim iStamp As Integer
Dim varAttributes As Variant
Dim strAttributes As String
Dim tagstr As String
Dim j As Integer

i = 1
Dim Layouts As AcadLayouts, Layout As AcadLayout
Dim N, k As Integer
Dim iTab As AcadTable
Dim MyItem As AcadEntity

'--------Экспорт в таблицу Excel-------------------
    Dim Excel As Object
    Dim elem As Object
    Dim excelSheet As Object
    Dim ExcelBook As Object
    
    ' Start Excel
    On Error Resume Next
    
    Set Excel = GetObject(, "Excel.Application")
    
    If Err <> 0 Then
        Err.Clear
        Set Excel = CreateObject("Excel.Application")
            
        If Err <> 0 Then
            MsgBox "Could not load Excel.", vbExclamation
            End
        End If
    End If
    
    On Error GoTo 0
'--------Формирование столбца простых имен (т.е. без формата листа)
'For N = 1 To i
'list(4, N) = Right(list(1, N), Len(list(1, N)) - InStr(1, list(1, N), " "))
'list(10, N) = list(7, N) & " " & list(8, N) & " " & list(9, N)
'Next N


    
    ' Создается лист1 в Excel
    
   Dim NFile
    
    'file = "C:\Program Files\AutoCAD 2006\Support\ШТАМП.xls" 'InputBox("Введите путь и имя сводной таблицы", , "C:\Program Files\AutoCAD 2005\Support\ШТАМП.xls")
    NFile = "C:\Users\Public\Documents\ListOfSpecS.xls" '"C:\ListOfWorkSheets.xls"
    Excel.Visible = False
    'Set ExcelBook = Excel.Workbooks.Open(file)
    Set ExcelBook = Excel.Workbooks.Open(NFile)
    'ExcelBook.Sheets("ШТАМП").Select
    'Set excelSheet = Excel.ActiveWorkbook.Sheets("ШТАМП")
    Set excelSheet = Excel.ActiveWorkbook.ActiveSheet
        '--------------------------------------------------------------------------------------------------------
        'Выделяем область для экспорта
        'Выделяются автоматически все непустые ячейки начиная с A1
        excelSheet.Activate
        excelSheet.Range("A1").Activate
        Excel.ActiveCell.CurrentRegion.Select
        Dim tbl
        Set tbl = Excel.ActiveCell.CurrentRegion
        tbl.Resize(tbl.Rows.Count, _
        tbl.Columns.Count).Select
'--------------------------------------------------------------------------------------------------------
Dim row, col As Long
'Dim ssetObj As AcadSelectionSet
'col = tbl.Columns.Count
'row = tbl.Rows.Count
'-----------------------------------
Dim list(0 To 10000, 1 To 50) As Variant
For row = 1 To tbl.Rows.Count ' переводим данные из Excel в Acad
    For col = 1 To tbl.Columns.Count
        s = tbl.cells(row, col)
        list(row, col) = s
    Next col
Next row
Nrows = tbl.Rows.Count
Ncols = tbl.Columns.Count
'---------------------------------------------------------------------

'excelSheet.Cells(1, 1).Value = "ФАЙЛ"
'excelSheet.Cells(1, 2).Value = "ЛИСТ"
'excelSheet.Cells(1, 3).Value = "№ листа в файле"
'excelSheet.Cells(1, 4).Value = "Шифр"
'excelSheet.Cells(1, 5).Value = "Адрес объекта"
'excelSheet.Cells(1, 6).Value = "Название подсистемы"
'excelSheet.Cells(1, 7).Value = "Название документа"
'excelSheet.Cells(1, 8).Value = "Поз."
'excelSheet.Cells(1, 9).Value = "Обозначение"
'excelSheet.Cells(1, 10).Value = "Наименование"
'excelSheet.Cells(1, 11).Value = "Кол."
'excelSheet.Cells(1, 12).Value = "Масса"
'excelSheet.Cells(1, 13).Value = "Примечание"
   
 i = 2
'--------------------------------------
'--------------------------------------
'ThisDrawing.Application.Visible = True
For Each File In ThisDrawing.Application.Documents
    File.Activate
    For Each Sheet In File.Layouts
        If Sheet.Name <> "Model" And Sheet.Name <> "Модель" Then
        l1 = 1
        While list(l1, 1) <> File.Name And list(l1, 2) <> Sheet.Name And l1 < Nrows
            l1 = l1 + 1
            Wend
        ' ищем таблицу с 6 графами на листе
        Index = 0
        Cols = 0
        Ntabs = 0
        Set MyItem = Sheet.Block.Item(Index)
        While Index < Sheet.Block.Count - 1 And Ntabs < 2 'Sheet.Block.Item(Index).ObjectName <> "AcDbTable" And Left(MyItem.GetText(0, 0), 3) <> "Поз" 'And Cols <> 6
            Index = Index + 1
            Set MyItem = Sheet.Block.Item(Index)
            If Sheet.Block.Item(Index).ObjectName = "AcDbTable" Then
                Ntabs = Ntabs + 1
                If Left(MyItem.GetText(0, 0), 3) <> "Обо" Then
                    Set iTab = MyItem
                    Cols = iTab.Columns
                End If
            End If
            Wend
        If Not (IsEmpty(iTab)) Then
            For row = 1 To iTab.Rows - 1
                For col = 0 To iTab.Columns - 1
                    iTab.SetText row, col, list(row + l1 - 1, col + 8)
                Next col
            Next row
        End If
        'row = row + iTab.Rows - 1
        End If
    Next Sheet
Next File
'    File.Close False
Excel.Quit
MsgBox "The Game Is Over :)"
Else    ' User chose No.
    MsgBox "Сделайте это..."
End If
End Sub

Sub One()

For row = 1 To Nrows
        ' ищем нужный файл лист и таблицу
        l1 = 0
        Fname = list(row, 1)
        Fcount = ThisDrawing.Application.Documents.Count
        Fname1 = ThisDrawing.Application.Documents.Item(l1).Name
        While Fname <> Fname1 And i1 <= Fcount ' ищем нужный файл в списке
            Set File = ThisDrawing.Application.Documents.Item(l1)
            Fname1 = File.Name
            l1 = l1 + 1
            Wend
        ThisDrawing.Application.Documents.Item(l1).Activate
        ' ищем нужный лист
        Set Layouts = ThisDrawing.Application.Documents.Item(l1).Layouts
        While list(l2, 2) <> Layouts.Item(l2).Name And l2 < Layouts.Count ' ищем нужный лист в списке
            l2 = l2 + 1
            Wend
        Set Sheet = Layouts.Item(l2)
        'If l2 <= tbl.Rows.Count Then
        ' ищем таблицу с 6 графами на листе
        Index = 0
        Cols = 0
        While Index < Sheet.Block.Count - 1 And MyItem.ObjectName <> "AcDbTable" <> 6
            Index = Index + 1
            Set MyItem = Sheet.Block.Item(Index)
            If MyItem.ObjectName = "AcDbTable" Then
                Set iTab = MyItem
                Cols = iTab.Columns
            End If
            Wend
        For row1 = 1 To iTab.Rows - 1
            For col = 0 To iTab.Columns
                iTab.SetText row, col, list(row1 + row - 1, col + 8)
            Next col
        Next row1
        row = row + iTab.Rows - 1
    Next row
End Sub
End Sub

Attribute VB_Name = "Plot"
Sub Plot_WorkSheets() ' печать листов в проекте
'--------проверка юзера------------------
Dim msg, Style, Title, Ctxt, Response, MyString
'--------------начало работы основной части программы------------
'Dim list(1 To 1000, 0 To 100) As Variant
'Dim Stamp As AcadBlockReference
'Dim iStamp As Integer
'Dim varAttributes As Variant
'Dim strAttributes As String
'Dim tagstr As String
Dim j As Integer
Dim l1, l2, l3, l4 As Integer
'---------------------------------------------------------------------------

Dim Layouts As AcadLayouts, Layout As AcadLayout
Dim N, k As Integer
Dim alignmentPoint(0 To 1), PaperWidth, PaperHeight As Double
Dim insPnt(0 To 2) As Double
Dim xName, FileName, FileNameA, FileNameB, FileNameC, FileNameD, FileName1, plotFileName As String

'--------------------------------------
    Dim oPlot As AcadPlot
    Dim AddedLayouts() As String
    Dim LayoutList As Variant
    Dim oLayout As AcadLayout
    Dim ArraySize As Integer, BatchCount As Integer
    Dim result As Boolean
'--------------------------------------
For Each File In ThisDrawing.Application.Documents
    '----------------------------
    Erase AddedLayouts()
    File.Activate
    ArraySize = 0
    '----------------------------
    Set Layouts = File.Layouts
    For Each Sheet In Layouts
        If Sheet.Name <> "Model" And Sheet.Name <> "Модель" Then
                ArraySize = 1 'ArraySize + 1
                ReDim Preserve AddedLayouts(1 To ArraySize)
                AddedLayouts(ArraySize) = Sheet.Name

                'File.Regen acAllViewports
                'Set BACKGROUNDPLOT = 0
                'File.Plot.PlotToFile (FileName)
                Sheet.GetPaperSize PaperWidth, PaperHeight
                Sheet.ConfigName = "DWG To PDF.pc3"
                Sheet.PlotType = acLayout
                ' А1, А2, А3, A4 -1, -1
                '
                If PaperWidth * PaperHeight = 297 * 210 Or _
                    PaperWidth * PaperHeight = 297 * 420 Or _
                    PaperWidth * PaperHeight = 420 * 594 Or _
                    PaperWidth * PaperHeight = 594 * 840 Then
                        alignmentPoint(0) = -1
                        alignmentPoint(1) = -1
                        Else
                        alignmentPoint(0) = 0
                        alignmentPoint(1) = 0
                    End If
                Sheet.PlotOrigin = alignmentPoint
                'File.Plot.PlotToDevice (FileName)
                'ZoomAll
                'ThisDrawing.Application.ZoomAll
                '-------------------------------------------------------PRINT
                'File.Regen acAllViewports
                
                'LayoutList = AddedLayouts
                'Set oPlot = ThisDrawing.Application.ActiveDocument.Plot
                'plotFileName = FileNameB & "_" & FileNameD & "."
                'oPlot.SetLayoutsToPlot LayoutList
                'result = oPlot.PlotToFile(plotFileName, "DWG To PDF.pc3")    'DWFx ePlot (XPS Compatible) Adobe PDF printer  Adobe PDFa_autoprint"DWG To PDF.pc3"
                
            End If
            
        Next Sheet
        
        
        '--------переименование и сохранение файла---------
        'xName = File.Name
        'FileName = FileNameA & "_" & FileNameB & "_" & xName '& FileNameC
        
        'xPath = Left(xName, Len(xName) - InStr(1, "\", StrReverse(xName)) + 1)
        'xName = xPath & FileName
        'File.SaveAs FileName
        
        'File.Close
                
Next File

MsgBox "The Game Is Over :)"
   
End Sub
